Attribute VB_Name = "Module1"
Sub autodraw()
UserForm1.Show
End Sub

Attribute VB_Name = "Rdexcel"
Sub rexcel()
Dim i, j As Integer: i = 0: j = 0
Dim a As Double
Dim str As String
Dim excelapp As Excel.Application '定义excle应用程序变量
Dim excelsheet As Worksheet '定义工作表变量
Set excelapp = CreateObject("excel.application")  '激活excel程序
excelapp.Workbooks.Open (excelpath) '打开工作薄
'读取站点数据
Set excelsheet = excelapp.ActiveWorkbook.Sheets("sheet1") '当前工作表为sheet1
'识别站数
Do While (excelsheet.Cells(i + 2, 2).Value <> "")
  i = i + 1
Loop
ReDim station(1 To i) As Double
For j = 0 To i - 1
station(j + 1) = excelsheet.Cells(j + 2, 2).Value
Next j
excelapp.Quit '退出excel程序
Set excelapp = Nothing '释放变量
Set excelsheet = Nothing
End Sub


Function GetFile(strTitle As String, strFilter As String, Optional strIniDir As String) As String
    On Error Resume Next
    
    Dim FileName As String
    Dim oFileBox As OPENFILENAME
    
    With oFileBox
        .lpstrTitle = strTitle '对话框标题
        .lpstrInitialDir = strIniDir '初始目录
        .lStructSize = Len(oFileBox)
        .hwndOwner = ThisDrawing.HWND
        .flags = OFN_PATHMUSTEXIST Or OFN_FILEMUSTEXIST Or OFN_HIDEREADONLY
        .lpstrFile = String$(255, 0)
        .nMaxFile = 255
        .lpstrFileTitle = String$(255, 0)
        .nMaxFileTitle = 255
        .lpstrFilter = strFilter  '过滤器
        .nFilterIndex = 1
    End With
    
    lntFile = GetOpenFileName(oFileBox) '执行打开对话框
    
    If lntFile <> 0 Then
        FileName = Left(oFileBox.lpstrFile, InStr(oFileBox.lpstrFile, vbNullChar) - 1)
        GetFile = FileName
    Else
        GetFile = ""
    End If
    
End Function

Sub plht()

Dim i, j As Integer: i = 1
Dim a As Double
Dim str As String

Dim excelapp As Excel.Application '定义excle应用程序变量
Dim excelsheet As Worksheet '定义工作表变量
Set excelapp = CreateObject("excel.application")  '激活excel程序
excelapp.Workbooks.Open (excelpath) '打开工作薄

For Each lay0 In ThisDrawing.Layers '在所有的图层中进行循环
If lay0.Name = "客车运行线" Then
    ThisDrawing.ActiveLayer = lay0
 End If
Next lay0
Set excelsheet = excelapp.ActiveWorkbook.Sheets("sheet2") '当前工作表为sheet2
Do While (excelsheet.Cells(i + 1, 3).Value <> "")
  Call drawtime(time2lenth(excelsheet.Cells(i + 1, 1).Value), time2lenth(excelsheet.Cells(i + 1, 2).Value), Int(excelsheet.Cells(i + 1, 3).Value), Int(excelsheet.Cells(i + 1, 4).Value))
    i = i + 1
Loop


i = 1
For Each lay0 In ThisDrawing.Layers '在所有的图层中进行循环
If lay0.Name = "直达货车运行线" Then
    ThisDrawing.ActiveLayer = lay0
 End If
Next lay0
Set excelsheet = excelapp.ActiveWorkbook.Sheets("sheet3") '当前工作表为sheet3
Do While (excelsheet.Cells(i + 1, 3).Value <> "")
  Call drawtime(time2lenth(excelsheet.Cells(i + 1, 1).Value), time2lenth(excelsheet.Cells(i + 1, 2).Value), Int(excelsheet.Cells(i + 1, 3).Value), Int(excelsheet.Cells(i + 1, 4).Value))
    i = i + 1
Loop

i = 1
For Each lay0 In ThisDrawing.Layers '在所有的图层中进行循环
If lay0.Name = "区段货车运行线" Then
    ThisDrawing.ActiveLayer = lay0
 End If
Next lay0
Set excelsheet = excelapp.ActiveWorkbook.Sheets("sheet4") '当前工作表为sheet4
Do While (excelsheet.Cells(i + 1, 3).Value <> "")
  Call drawtime(time2lenth(excelsheet.Cells(i + 1, 1).Value), time2lenth(excelsheet.Cells(i + 1, 2).Value), Int(excelsheet.Cells(i + 1, 3).Value), Int(excelsheet.Cells(i + 1, 4).Value))
    i = i + 1
Loop

i = 1
For Each lay0 In ThisDrawing.Layers '在所有的图层中进行循环
If lay0.Name = "摘挂货车运行线" Then
    ThisDrawing.ActiveLayer = lay0
 End If
Next lay0
Set excelsheet = excelapp.ActiveWorkbook.Sheets("sheet5") '当前工作表为sheet5
Do While (excelsheet.Cells(i + 1, 3).Value <> "")
  Call drawtime(time2lenth(excelsheet.Cells(i + 1, 1).Value), time2lenth(excelsheet.Cells(i + 1, 2).Value), Int(excelsheet.Cells(i + 1, 3).Value), Int(excelsheet.Cells(i + 1, 4).Value))
    i = i + 1
Loop

ZoomAll
'ZoomExtents
excelapp.Quit '退出excel程序
Set excelapp = Nothing '释放变量
Set excelsheet = Nothing
End Sub

Attribute VB_Name = "UserForm1"
Attribute VB_Base = "0{655834D8-94DC-4304-B95F-23EB4AB0667C}{AC27A429-DB8E-4DD9-91D3-64066FBA0A7E}"
Attribute VB_GlobalNameSpace = False
Attribute VB_Creatable = False
Attribute VB_PredeclaredId = True
Attribute VB_Exposed = False
Attribute VB_TemplateDerived = False
Attribute VB_Customizable = False

Private Sub CommandButton1_Click()
Me.Hide
UserForm2.Show
End Sub

Private Sub CmdDraw_Click()
Me.Hide
UserForm3.Show
ZoomExtents
End Sub
Private Sub Cmdstart_Click()

Dim lay0, lay1, lay2 As AcadLayer '定义作为图层的变量
  '在所有的图层中进行循环
  
  

 For Each lay0 In ThisDrawing.Layers
 If lay0.Name = "格1" Then
    lay0.Linetype = "continuous"
 End If
 Next lay0
   For Each lay1 In ThisDrawing.Layers
 If lay1.Name = "格2" Then
     lay1.Linetype = "continuous"
     lay1.Lineweight = acLnWt030
 End If
 Next lay1
  For Each lay2 In ThisDrawing.Layers
 If lay2.Name = "格3" Then
 lay2.Linetype = "ACAD_ISO03W100"
 End If
 Next lay2
  

  

 

'++++++++++下面开始画网格++++++++++++
Dim i, j As Integer
Dim StartPoint(0 To 2) As Double     ' 定义起点坐标
Dim EndPoint(0 To 2) As Double
'+++++++++画1440分钟的竖线++++++++++++++  10min=100
For i = 0 To 144
StartPoint(0) = i * 100
StartPoint(1) = station(1) * 100
StartPoint(2) = 0
EndPoint(0) = i * 100
EndPoint(1) = station(UBound(station)) * 100
EndPoint(2) = 0

Select Case (i Mod 6)
Case 0
   For Each lay0 In ThisDrawing.Layers
 If lay0.Name = "格1" Then
    ThisDrawing.ActiveLayer = lay0
 End If
 Next lay0
Case 1, 2, 4, 5
  For Each lay0 In ThisDrawing.Layers
 If lay0.Name = "格2" Then
    ThisDrawing.ActiveLayer = lay0
 End If
 Next lay0
  Case 3
  For Each lay0 In ThisDrawing.Layers
 If lay0.Name = "格3" Then
    ThisDrawing.ActiveLayer = lay0
 End If
 Next lay0
 End Select

Call draw(StartPoint(), EndPoint())
Next i



'+++++++++画2分钟的横线++++++++++++++
  For Each lay0 In ThisDrawing.Layers
 If lay0.Name = "格1" Then
    ThisDrawing.ActiveLayer = lay0
 End If
 Next lay0
For j = 1 To UBound(station)
StartPoint(0) = 0
StartPoint(1) = station(j) * 100
StartPoint(2) = 0
EndPoint(0) = 144 * 100
EndPoint(1) = station(j) * 100
EndPoint(2) = 0
Call draw(StartPoint(), EndPoint())
Next j

ZoomExtents
End Sub


Private Sub CommandButton2_Click()
Me.Hide
UserForm4.Show
End Sub

Private Sub CommandButton3_Click()
 Call plht
End Sub

Private Sub UserForm_Initialize()
Dim find1, find2, find3, find4 As Boolean
find1 = False
find2 = False
find3 = False
find4 = False
startTime = 0
Dim lay0 As AcadLayer '定义作为图层的变量
 For Each lay0 In ThisDrawing.Layers '在所有的图层中进行循环
 If lay0.Name = "格1" Then
   find1 = True
 End If
  If lay0.Name = "格2" Then
   find2 = True
 End If
  If lay0.Name = "格3" Then
   find3 = True
 End If
 If lay0.Name = "运行线" Then
   find4 = True
 End If
 Next lay0
 
 If find1 = False Then
 ThisDrawing.Layers.Add ("格1")
 End If
  If find2 = False Then
 ThisDrawing.Layers.Add ("格2")
 End If
   If find3 = False Then
 ThisDrawing.Layers.Add ("格3")
 End If
 If find4 = False Then
 ThisDrawing.Layers.Add ("运行线")
 End If
 

End Sub

Attribute VB_Name = "UserForm2"
Attribute VB_Base = "0{B23F916F-F46D-4760-A57B-5E5756975874}{2EB48203-3D22-4B15-ABC3-C7F1B9DE0EE5}"
Attribute VB_GlobalNameSpace = False
Attribute VB_Creatable = False
Attribute VB_PredeclaredId = True
Attribute VB_Exposed = False
Attribute VB_TemplateDerived = False
Attribute VB_Customizable = False
Private Sub Cmd_Cancel_Click()
Me.Hide
'UserForm1.Show
End Sub

Private Sub Cmd_OK_Click()
Dim i As Integer
ReDim station(4)
station(1) = TextBox1.Text
station(2) = TextBox2.Text
station(3) = TextBox3.Text
Me.Hide
UserForm1.Show
End Sub

Attribute VB_Name = "UserForm3"
Attribute VB_Base = "0{6CA89252-0716-4158-8DA9-E0B4B389C1D0}{0B9EDFAB-AE46-4EBF-8BF4-B8AF0A7D858B}"
Attribute VB_GlobalNameSpace = False
Attribute VB_Creatable = False
Attribute VB_PredeclaredId = True
Attribute VB_Exposed = False
Attribute VB_TemplateDerived = False
Attribute VB_Customizable = False
Private Sub CommandButton1_Click()

Dim lay0 As AcadLayer '定义作为图层的变量
 For Each lay0 In ThisDrawing.Layers '在所有的图层中进行循环
 If lay0.Name = "运行线" Then
    ThisDrawing.ActiveLayer = lay0
 End If
 Next lay0
 
Dim date1, date2 As Variant
Dim length1, length2 As Variant
Dim temp As String
temp = TextBox1.Text & ":" & TextBox2.Text & ""
date1 = Format("00:00", CDate(temp))
'date2=FormatdateTime('tt',temp)
temp = TextBox4.Text & ":" & TextBox5.Text & ""
date2 = Format("00:00", CDate(temp))
length1 = time2lenth(date1)
length2 = time2lenth(date2)
Call drawtime(length1, length2, Int(TextBox7.Text), Int(TextBox8.Text))
ZoomAll
ZoomExtents
End Sub

Private Sub CommandButton2_Click()
Me.Hide
UserForm1.Show
End Sub

Attribute VB_Name = "UserForm4"
Attribute VB_Base = "0{A899F463-5920-49EB-846D-BA73A01E7AC4}{D4CA9DB9-90C3-4D93-A07C-952EE68EF83E}"
Attribute VB_GlobalNameSpace = False
Attribute VB_Creatable = False
Attribute VB_PredeclaredId = True
Attribute VB_Exposed = False
Attribute VB_TemplateDerived = False
Attribute VB_Customizable = False
Private Sub CommandButton1_Click()
 excelpath = GetFile("打开Excel表", "Excel文件" & vbNullChar & "*.xlsx")
 lblexcel.Caption = excelpath
End Sub

Private Sub CommandButton2_Click()
Call rexcel
Me.Hide
UserForm1.Show
End Sub

Private Sub CommandButton3_Click()
Me.Hide
UserForm1.Show
End Sub

Attribute VB_Name = "模块1"
Public startTime As Date     '定义起始的时间
Public excelpath As String  'Excel 文件路径
Public station() As Double    '定义站间距函数 调试时为3

Public Declare Function GetOpenFileName Lib "comdlg32.dll" Alias "GetOpenFileNameA" _
    (pOpenfilename As OPENFILENAME) As Long

Public Type OPENFILENAME
    lStructSize As Long
    hwndOwner As Long '拥有对话框的窗口
    hInstance As Long
    lpstrFilter As String '装载文件过滤器的缓冲区
    lpstrCustomFilter As String
    nMaxCustFilter As Long
    nFilterIndex As Long
    lpstrFile As String
    nMaxFile As Long
    lpstrFileTitle As String
    nMaxFileTitle As Long
    lpstrInitialDir As String
    lpstrTitle As String '对话框的标题
    flags As Long
    nFileOffset As Integer
    nFileExtension As Integer
    lpstrDefExt As String
    lCustData As Long
    lpfnHook As Long
    lpTemplateName As String
End Type

'将时间转化为长度
Function time2lenth(time As Variant) As Double
Dim a As Variant
Dim datetime As Date
datetime = Format("00:00", CDate(time))
a = DateDiff("n", startTime, datetime)
time2lenth = a * 10
End Function

Sub draw(StartPoint() As Double, EndPoint() As Double)
Dim LineObj As AcadLine          ' 定义Line对象
' 设置Line对象
Set LineObj = ThisDrawing.ModelSpace.AddLine(StartPoint, EndPoint)
End Sub

Sub drawtime(a As Variant, b As Variant, i As Integer, j As Integer)
Dim StartPoint(0 To 2) As Double     ' 定义起点坐标
Dim EndPoint(0 To 2) As Double
StartPoint(0) = a
StartPoint(1) = station(i) * 100
StartPoint(2) = 0
EndPoint(0) = b
EndPoint(1) = station(j) * 100
EndPoint(2) = 0
Call draw(StartPoint(), EndPoint())

End Sub
Sub hzwg()
Dim lay0 As AcadLayer '定义作为图层的变量
 For Each lay0 In ThisDrawing.Layers '在所有的图层中进行循环
 If lay0.Name = "格" Then
    ThisDrawing.ActiveLayer = lay0
 End If
 Next lay0

'++++++++++下面开始画网格++++++++++++
Dim i, j As Integer
Dim StartPoint(0 To 2) As Double     ' 定义起点坐标
Dim EndPoint(0 To 2) As Double
'+++++++++画2分钟的竖线++++++++++++++  先画20条
For i = 0 To 10
StartPoint(0) = i * 20
StartPoint(1) = 0
StartPoint(2) = 0
EndPoint(0) = i * 20
EndPoint(1) = station(UBound(station))
EndPoint(2) = 0
Call draw(StartPoint(), EndPoint())
Next i

StartPoint(0) = 0
StartPoint(1) = 0
StartPoint(2) = 0
EndPoint(0) = i * 20
EndPoint(1) = 0
EndPoint(2) = 0
Call draw(StartPoint(), EndPoint())

'+++++++++画2分钟的横线++++++++++++++
For j = 1 To UBound(station)
StartPoint(0) = 0
StartPoint(1) = station(j)
StartPoint(2) = 0
EndPoint(0) = i * 20
EndPoint(1) = station(j)
EndPoint(2) = 0
Call draw(StartPoint(), EndPoint())
Next j

ZoomExtents
End Sub
